# Specification: Specification Document
- Description: Anforderungen

## R1 (Headline)
Variablen

### REQ-1 (Test Case Type)
Alle Variablen, die direkt oder indirekt Teil des sichtbaren Zustands eines Objektes sind, müssen als final deklariert werden.
- Spec Relation Type -> TST-1

#### REQ-3 (Test Case Type)
Variablen, die nicht `private` sind, müssen `final` sein.
- Spec Relation Type -> TST-2

#### REQ-7 (Test Case Type)

### REQ-2 (Test Case Type)
Variablen mit einem veränderlichen Datentyp müssen als private deklariert werden.

### REQ-4 (Test Case Type)
Objekte müssen ordnungsgemäß erzeugt werden (properly constructed).

### REQ-5 (Test Case Type)
Verzögerte Initialisierung (lazy initialisation) einer Variable erhält die Immutability-Eigenschaft einer Klasse.
- Spec Relation Type -> TST-4

## R42 (Headline)
Klassenvererbung

### REQ-6 (Test Case Type)
Eine Klasse, die Vererbung zulässt (nicht `final`), sonst aber immutable ist, gilt als "schwach immutable".

## R43 (Headline)
Konstruktorparameter

### REQ-8 (Test Case Type)
Konstruktorparameter mit primitivem Datentyp dürfen Variablen direkt zugewiesen werden.
- links to -> TST-15

### REQ-26 (Test Case Type)
Von Konstruktorparametern mit veränderlichem Referenzdatentyp dürfen nur defensive Kopien Variablen zugewiesen werden.
- links to -> TST-19
- links to -> TST-8

## R46 (Headline)
Entweichen der This-Referenz

### REQ-11 (Test Case Type)
Der Aufruf einer Methode einer anderen Klasse mit `this` ist nicht gestattet.
- links to -> TST-17
- links to -> TST-38

### REQ-14 (Test Case Type)
Die this-Referenz darf keiner sichtbaren Variable direkt oder indirekt zugewiesen werden.
- links to -> TST-18
- links to -> TST-24
- links to -> TST-32
- links to -> TST-37
- links to -> TST-34

### REQ-17 (Test Case Type)
Im Konstruktor einer immutablen Klasse darf kein Konstruktor einer anderen Klasse mit `this` aufgerufen werden.
- links to -> TST-27
- links to -> TST-36
- links to -> TST-55

### REQ-18 (Test Case Type)
Die This-Referenz darf nicht indirekt durch eine statische Methode zurückgegeben werden.
- links to -> TST-28

### REQ-19 (Test Case Type)
Die This-Referenz darf keiner sichtbaren Instanzvariablen im Konstruktor zugewiesen werden.
- links to -> TST-18
- links to -> TST-33

### REQ-23 (Test Case Type)
Eine Klasse, welche Klassenvererbung gestattet, darf in ihrem Konstruktor keine überschreibbare Instanzmethode aufrufen, da Subklassen darin die `this`-Referenz veröffentlichen könnten.
- links to -> TST-43
- links to -> TST-23

## R69 (Headline)
Methoden

### REQ-20 (Test Case Type)
Methoden dürfen keine Seiteneffekte verursachen, welche sich auf den sichtbaren Zustand eines Objektes auswirken.
- links to -> TST-29
- links to -> TST-30
- links to -> TST-31

### REQ-25 (Test Case Type)
Die Klasse darf keine Setter-Methoden anbieten.
- links to -> TST-7
- links to -> TST-52

### REQ-28 (Test Case Type)
Native Methoden zerstören die Immutability-Eigenschaft einer Klasse.

# Specification
- Description: Tests

## R5 (Headline)
Variablen

### TST-1 (Test Case Type)
Sichtbare Variablen mit primitiven und Referenzdatentypen, die nicht als `final` deklariert sind.
- 0.8.0: passed
- Testklasse: VisibleNonFinalVariablesTest
- Note: `NON_FINAL_FIELD`, `PUBLISHED_NON_FINAL_FIELD`
- Expected: Jede Variable wird als Verletzung der Immutability-Eigenschaft erkannt.

### TST-2 (Test Case Type)
Private Variablen mit primitiven und Referenzdatentypen, die nicht als `final` deklariert sind und die nicht durch Methoden veröffentlicht werden.
- Note: Wird als *effectively immutable* erkannt.
- Testklasse: PrivateNonFinalVariablesTest
- Expected: Keine der Variablen wird als Verletzung der Immutability-Eigenschaft erkannt.
- 0.8.0: passed

### TST-3 (Test Case Type)
Veränderliche Datentypen müssen sicher gekapselt werden (`System.currentTimeMillis()`).

### R38 (Headline)
Sichere Kapselung

#### TST-11 (Test Case Type)
Klasse mit einer privaten, finalen Instanzvariable vom Typ int-Array, die nach der Konstruktion keine Änderungen daran vornimmt.
- 0.8.0: failed
- Expected: Klasse wird als *immutable* erkannt.
- Note: `MUTABLE_TYPE_TO_FIELD`, `ARRAY_TYPE_INHERENTLY_MUTABLE`
- Testklasse: WithPrivateFinalIntArray

#### TST-12 (Test Case Type)
Klasse mit einer privaten, finalen Instanzvariable vom Typ Date-Array, die nach der Konstruktion keine Änderungen daran vornimmt.
- 0.8.0: failed
- Expected: Klasse wird als *immutable* erkannt.
- Testklasse: WithPrivateFinalDateArray
- Note: `MUTABLE_TYPE_TO_FIELD`, `ARRAY_TYPE_INHERENTLY_MUTABLE`

#### TST-16 (Test Case Type)
Klasse mit einem Getter für eine Instanzvariable mit mutablen Typ ohne defensive Kopie.
- Note: Klasse wird zwar als mutable erkannt, jedoch aus dem falschen Grund: Weil überhaupt eine Variable mit veränderlichem Typ verwendet wird.
- Expected: Klasse wird als *mutable* erkannt, da eine defensive Kopie zurückgegeben werden muss.
- Testklasse: DirectReturnOfMutableType
- 0.8.0: failed

#### TST-21 (Test Case Type)
Klasse mit einem Getter für eine Instanzvariable mit mutablen Typ mit defensiver Kopie.
- Note: `MUTABLE_TYPE_TO_FIELD`
- Expected: Klasse wird als *immutable* erkannt, da vor der Rückgabe des mutablen Typs eine defensive Kopie angefertigt wird.
- Testklasse: IndirectReturnOfMutableType
- 0.8.0: failed

## R22 (Headline)
Klassenvererbung

### TST-5 (Test Case Type)
Schwach immutable Klasse, welche Klassenvererbung zulässt (d. h. nicht `final` ist).
- 0.8.0: failed
- Expected: Die Klasse wird als *immutable* erkannt.
- Testklasse: WeakImmutableSuperclass

### TST-6 (Test Case Type)
Immutable Klasse, welche von einer anderen immutablen Klasse abgeleitet ist.
- 0.8.0: passed
- Expected: Die Klasse wird als *immutable* erkannt.
- Testklasse: ImmutableSubclass

### TST-46 (Test Case Type)
Klasse, die von `WeakImmutableSuperclass` abgeleitet ist, selbst jedoch mutable ist.
- Testklasse: MutableSubclass
- Expected: Die Klasse wird als *mutable* erkannt.
- 0.8.0: passed

### TST-47 (Test Case Type)
Finale Klasse, die von einer mutablen Superklasse abgeleitet ist.
- Note: Die Klasse wird als *immutable* erkannt.
- Testklasse: ExtendingMutableSuperclass
- Expected: Die Klasse wird als *mutable* erkannt, da ihr Supertyp auch mutable ist.
- 0.8.0: failed

### TST-51 (Test Case Type)
Finale Klasse, die von einer abstrakten Superklasse abgeleitet ist.
- Note: Die Klasse wird als *immutable* erkannt.
- Testklasse: SubclassOfAbstractClass
- Expected: Die Klasse wird als *mutable* erkannt, da ihr Supertyp auch mutable ist.
- 0.8.0: failed

## R39 (Headline)
Typen

### TST-48 (Test Case Type)
Enum mit Getter-Methode für eine immutable Instanzvariable.
- Testklasse: ImmutableEnumType
- Expected: Die Enum wird als *immutable* erkannt.
- 0.8.0: passed

### TST-49 (Test Case Type)
Interface ohne Methodendeklarationen (Marker-Interface).
- Testklasse: MarkerInterface
- Expected: Das Interface wird als *mutable* erkannt, da vom Interface nicht auf die verschiedenen Implementierungen geschlossen werden kann.
- 0.8.0: passed

### TST-50 (Test Case Type)
Abstrakte Klasse, die ine abstrakte Methode definiert.
- Testklasse: AbstractClass
- Expected: Die Klasse wird als *mutable* erkannt, da nicht auf die verschiedenen Implementierungen geschlossen werden kann.
- 0.8.0: passed

### TST-14 (Test Case Type)
Klasse mit einer privaten, finalen Instanzvariable, die als statischen Typ ein Interface hat. Über den Konstruktor wird dieser Variablen eine immutable Klasse zugewiesen
- Expected: Klasse wird als *immutable* erkannt.
- Testklasse: RelyingOnInterfaceAsStaticType
- 0.8.0: passed

## R23 (Headline)
Verzögerte Initialisierung (Lazy Initialization)

### TST-4 (Test Case Type)
Private Variable mit primitivem Datentyp, die nicht als `final` deklariert ist, die durch eine Methode veröffentlicht wird und die genau einmal nach der Konstruktion des Objektes initialsiert wird.
- 0.8.0: failed
- Testklasse: BasicLazyInitialisation
- Note: Dieses Muster ist Teil von Lazy Initialisation.
- Expected: Die Klasse wird als *immutable* erkannt.

## R28 (Headline)
Konstruktoren

### TST-8 (Test Case Type)
Direkte Zuweisung eines mutablen Datentyps an eine Instanzvariable durch den Konstruktor.
- 0.8.0: failed
- Expected: Klasse wird aufgrund der direkten Zuweisung als mutable erkannt.
- Note: Klasse wird zwar als mutable erkannt, jedoch aus dem falschen Grund: Weil überhaupt eine Variable mit veränderlichem Typ verwendet wird.
- Testklasse: DirectAssignmentOfMutableType

### TST-15 (Test Case Type)
Direkte Zuweisung eines primitiven Datentyps an eine Instanzvariable durch den Konstruktor.
- 0.8.0: passed
- Expected: Die Klasse wird als *immutable* erkannt.
- Testklasse: DirectAssignmentOfPrimitiveType

### TST-19 (Test Case Type)
Zuweisung einer defensiven Kopie an einen mutablen Datentyp.
- Note: `MUTABLE_TYPE_TO_FIELD`
- Expected: Die Klasse wird als *immutable* erkannt.
- Testklasse: IndirectAssignmentOfMutableType
- 0.8.0: failed

## R30 (Headline)
Transitivität

### TST-9 (Test Case Type)
Klasse, die eine immutable Klasse verwendet.
- 0.8.0: passed
- Expected: Die Klasse wird als *immutable* erkannt.
- Testklasse: TransitiveImmutable

### TST-10 (Test Case Type)
Klasse, die eine mutable Klasse verwendet.
- 0.8.0: passed
- Expected: Die Klasse wird als *mutable* erkannt.
- Testklasse: TransitiveMutable

## R24 (Headline)
Methoden

### TST-7 (Test Case Type)
Klasse, mit typischen Getter- und Setter-Methoden.
- 0.8.0: passed
- Expected: Die Klasse wird als *mutable* erkannt, da eine Wertzuweisung von außen nach der Objekterzeugung erfolgt. Grund für Mutability sei die Methode `setRate`.
- Testklasse: BeanLike

### TST-52 (Test Case Type)
Klasse mit einer privaten, finalen und statischen Collection, welche über eine sichtbare Methode geändert werden kann.
- Note: Die Klasse wird als *immutable* erkannt.
- Testklasse: Fakeout
- Expected: Die Klasse wird als *mutable* erkannt, da sich der sichtbare Zustand von Instanzen nach deren Erzeugung ändern kann (`setAge`).
- 0.8.0: failed

### TST-29 (Test Case Type)
Klasse mit einer Methode, welche absichtlich und offensichtlich einen Seiteneffekt auslöst.
- Note: MD bemängelt auch, dass die Variable `counter` nicht `final` ist.
- Expected: Klasse wird als *mutable* erkannt, da die Methode einen Seiteneffekt auslöst, welcher den sichtbaren Zustand des Objektes ändert.
- 0.8.0: passed
- Testklasse: WithObviousSideEffect

### TST-30 (Test Case Type)
Klasse mit einer Methode, welche den Wert einer Instanzvariable ändert, die indirekt zum sichtbaren Objektzustand gehört.
- Note: MD bemängelt auch, dass die Variable `invokationCounter` nicht `final` ist.
- Expected: Klasse wird als *mutable* erkannt, da die Methode einen Seiteneffekt auslöst, welcher den sichtbaren Zustand des Objektes ändert.
- 0.8.0: passed
- Testklasse: WithObliqueSideEffect

### TST-31 (Test Case Type)
Klasse mit einer Methode, die den Wert einer Instanzmethode ändert, welche zum verborgenen Objektzustand gehört.
- Note: MD erkennt die Klasse als *mutable*, da die Variable `invokationCounter` nicht `final` ist (`NON_FINAL_FIELD`) und der Wert der Variablen in Methode `getValue` neu zugewiesen wird (`FIELD_CAN_BE_REASSIGNED`).
- Expected: Klasse wird als *immutable* erkannt, da das Ändern des verborgenen Objektzustands die Immutability-Eigenschaft nicht verletzt.
- 0.8.0: failed
- Testklasse: WithSideEffectOnHiddenObjectState

### TST-56 (Test Case Type)
Klasse mit nativen Methoden.
- Testklasse: System
- 0.8.0: failed
- Expected: Die Klasse wird als *mutable* erkannt, da nicht festgestellt werden kann, ob die native Implementierung die Immutability-Eigenschaft verletzt.
- Note: Die Klasse wird als *immutable* erkannt.

## R50 (Headline)
Entweichen der This-Referenz

### TST-17 (Test Case Type)
Klasse, die in ihrem Konstruktor eine Klassenmethode einer anderen Klasse explizit mit `this` aufruft.
- 0.8.0: passed
- Expected: Die Klasse wird als *mutable* erkannt, da die this-Referenz entweicht.
- Testklasse: InvokeAlienMethodWithThis

### TST-38 (Test Case Type)
Klasse, die in ihrem Konstruktor eine Instanzmethode einer anderen Klasse explizit mit `this` aufruft.
- 0.8.0: failed
- Expected: Die Klasse wird als *mutable* erkannt, da die this-Referenz entweicht.
- Testklasse: PassThisReferenceToParameter

### TST-18 (Test Case Type)
Klasse, welche im Konstruktor die this-Referenz einer sichtbaren Instanzvariable der selben Klasse direkt zuweist.
- 0.8.0: passed
- Expected: Die Klasse wird als *mutable* erkannt, da die this-Referenz entweicht.
- Testklasse: SaveThisReferenceAsInstanceFieldOfThisClass

### TST-34 (Test Case Type)
Klasse, welche im Konstruktor die this-Referenz einer sichtbaren Instanzvariable einer anderen Klasse direkt zuweist.
- 0.8.0: passed
- Expected: Die Klasse wird als *mutable* erkannt, da die this-Referenz entweicht.
- Testklasse: SaveThisReferenceAsInstanceFieldOfThisObject

### TST-23 (Test Case Type)
Nicht-finale Klasse, in deren Konstrukor eine überschreibbare Instanzmethode aufgerufen wird.
- Note: Die Klasse wird auch als *mutable* erkannt, weil diese nicht `final` ist.
- Expected: Die Klasse wird als *immutable* erkannt, da die this-Referenz erst nach der vollständigen Konstruktion veröffentlicht wird.
- Testklasse: InvokeOverridableInstanceMethod
- 0.8.0: failed

### TST-24 (Test Case Type)
Klasse, welche im Konstruktor die this-Referenz einer sichtbaren Klassenvariable in der selben Klasse direkt zuweist.
- Expected: Die Klasse wird als *mutable* erkannt, da die this-Referenz entweicht.
- Testklasse: SaveThisReferenceAsStaticFieldOfThisClass
- 0.8.0: passed

### TST-35 (Test Case Type)
Klasse, welche im Konstruktor die this-Referenz einer sichtbaren Klassenvariable einere anderen Klasse direkt zuweist.
- 0.8.0: passed
- Expected: Die Klasse wird als *mutable* erkannt, da die this-Referenz entweicht.
- Testklasse: SetThisReferenceAsStaticFieldOfOtherClass

### TST-25 (Test Case Type)
Klasse, in deren Konstruktor ein Thread gestartet wird, welcher eine implizite this-Referenz hält.
- Expected: Die Klasse wird als *mutable* erkannt, da die this-Referenz entweicht.
- Testklasse: StartingThreadWithImplicitThisReference
- 0.8.0: passed

### TST-26 (Test Case Type)
Klasse, in deren Konstruktor ein Thread gestartet wird, welcher keine Probleme verursacht.
- Expected: Die Klasse wird als *immutable* erkannt.
- Testklasse: StartingBenignThread
- 0.8.0: passed

### TST-28 (Test Case Type)
Klasse mit einer Klassenmethode, die die `this`-Referenz indirekt zurückgibt, welche
- Expected: Die Klasse wird als *mutable* erkannt, da die this-Referenz entweicht.
- Testklasse: ReturningThisFromMethod
- 0.8.0: passed

### TST-32 (Test Case Type)
Klasse, welche im Konstruktor die `this`-Referenz einer sichtbaren statischen Collection von sich selbst hinzufuegt.
- Expected: Die Klasse wird als *mutable* erkannt, da die this-Referenz entweicht.
- 0.8.0: passed
- Testklasse: AddingThisToVisibleCollection

### TST-37 (Test Case Type)
Klasse, welche im Konstruktor die `this`-Referenz einer statischen sichtbaren Collection einer anderen Klasse hinzufuegt.
- 0.8.0: passed
- Expected: Die Klasse wird als *mutable* erkannt, da die this-Referenz entweicht.
- Testklasse: PassThisReferenceToStaticObject

### TST-27 (Test Case Type)
Klasse, in deren Konstruktor ein anderer Konstruktor mit `this` aufgerufen wird.
- Expected: Die Klasse wird als *mutable* erkannt, da die this-Referenz entweicht.
- Testklasse: CallingConstructorWithThis
- 0.8.0: passed

### TST-33 (Test Case Type)
Klasse, in deren Konstruktor `this` an eine Instanzvariable einer anderen Klasse zugewiesen wird.
- 0.8.0: passed
- Expected: Die Klasse wird als *mutable* erkannt, da die this-Referenz entweicht.
- Testklasse: AssigningThisToAlienInstanceVariable

### TST-36 (Test Case Type)
Klasse, die in ihrem Konstruktor einen Alias der this-Referenz an einen Konstruktor einer fremden Klasse übergibt.
- Note: Die Klasse wird als *immutable* erkannt.
- 0.8.0: failed
- Expected: Die Klasse wird als *mutable* erkannt, da die this-Referenz entweicht.
- Testklasse: AliasesThisReferenceBeforeLettingItEscape

### TST-39 (Test Case Type)
Klasse, die in ihrem Konstruktor eine anonyme lokale Klasse als Parameter an eine Instanzmethode einer fremden Klasse übergibt.
- 0.8.0: passed
- Expected: Die Klasse wird als *mutable* erkannt, da die this-Referenz entweicht.
- Testklasse: PassAnonymousInnerClassWithImplicitReferenceToThis

### TST-40 (Test Case Type)
Klasse, die in ihrem Konstruktor eine innere Klasse als Parameter an eine Instanzmethode einer fremden Klasse übergibt.
- 0.8.0: passed
- Expected: Die Klasse wird als *mutable* erkannt, da die this-Referenz entweicht.
- Testklasse: PassInnerClassWithImplicitReferenceToThis

### TST-41 (Test Case Type)
Finale Klasse, die in ihrem Konstruktor eine Instanzmethode aufruft. Diese Instanzmethode veröffentlicht einen Alias der this-Referenz.
- Note: Die Klasse wird als *immutable* erkannt.
- 0.8.0: failed
- Expected: Die Klasse wird als *mutable* erkannt, da die this-Referenz entweicht.
- Testklasse: AliasesThisReferenceInInstanceMethod

### TST-43 (Test Case Type)
Klasse, die in ihrem Konstruktor eine nicht-überschreibbare Instanzmethode aufruft. Die this-Referenz der Klasse kann nicht entweichen. Die Klasse lässt Vererbung zu.
- Testklasse: InvokeFinalInstanceMethod
- Expected: Die Klasse wird als *immutable* erkannt, da die this-Referenz nicht entweichen kann.
- 0.8.0: passed

### TST-44 (Test Case Type)
Finale Klasse, die in ihrem Konstruktor die this-Referenz in einer privaten finalen Instanzvariable speichert.
- Note: Die Klasse wird als *mutable* erkannt, da die this-Referenz während der Konstruktion entweicht.
- Testklasse: SaveThisReferenceToPrivateInstanceField
- Expected: Die Klasse wird als *immutable* erkannt, da die this-Referenz nicht entweichen kann.
- 0.8.0: failed

### TST-45 (Test Case Type)
Finale Klasse, die in einem ihrer Konstruktoren einen anderen eigenen Konstruktor aufruft, die this-Referenz dabei jedoch nicht entweichen lässt.
- Testklasse: CallToOtherConstructor
- Expected: Die Klasse wird als *immutable* erkannt, da die this-Referenz nicht entweichen kann.
- 0.8.0: passed

### TST-54 (Test Case Type)
Klasse, die in ihrem Konstruktor eine Instanzvariable initialisierung und diese anschließend an den Konstruktor einer fremden Klasse übergibt.
- 0.8.0: passed
- Testklasse: PassesInitialisedFieldToOtherMethod
- Expected: Die Klasse wird als *immutable* erkannt, da die this-Referenz nicht entweichen kann.
- Note: Die Klasse wird zwar als *mutable* erkannt, jedoch nur, weil der Typ `Object` mutable ist.

### TST-55 (Test Case Type)
Klasse mit zwei Konstruktoren. In einem der Konstruktoren wird die this-Referenz explizit als Parameter an den Konstruktor einer anderen Klasse übergeben.
- 0.8.0: failed
- Testklasse: InOneConstructorButNotTheOther
- Expected: Die Klasse wird als *mutable* erkannt, da die this-Referenz bei einem Konstruktor entweicht.
- Note: Die Klasse wird als *immutable* erkannt.

## R97 (Headline)
Verschiedenes

### TST-53 (Test Case Type)
- Note: Die Klasse wird als *effektiv immutable* erkannt, da die Instanzvariablen nicht ´final´ sind.
- Testklasse: ImmutableUsingPrivateFieldSettingMethod
- Expected: Die Klasse wird als *immutable* erkannt, da sich der sichtbare Zustand der Instanzen nach der Konstruktion nicht mehr ändert.
- 0.8.0: passed

## R4 (Headline)
Anforderungen zur Erfüllung der Immutability-Eigenschaft

## TST-1 (Test Case Type)
- 0.8.0: passed

## REQ-10 (Test Case Type)
Verzögerte Initialisierung (lazy initialisation) muss möglich sein ohne die Immutability-Eigenschaft zu zuerstören.

## REQ-11 (Test Case Type)

## R17 (Headline)
Klassenvererbung

## R21 (Headline)
Klassenvererbung

## R26 (Headline)
Konstruktoren

## REQ-20 (Test Case Type)

## R34 (Headline)
Verschiedenes

## REQ-25 (Test Case Type)

## REQ-26 (Test Case Type)

## R40 (Headline)
Klassenvererbung

## R48 (Headline)
Entweichen der This-Referenz

## REQ-12 (Test Case Type)

## REQ-13 (Test Case Type)

## REQ-16 (Test Case Type)

## TST-22 (Test Case Type)

## REQ-21 (Test Case Type)

## TST-42 (Test Case Type)
Tests für die Klassen in `Safe.java`.

## REQ-22 (Test Case Type)

## REQ-24 (Test Case Type)

## REQ-27 (Test Case Type)

## R106 (Headline)

## REQ-29 (Test Case Type)
